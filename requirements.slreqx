# requirements

## H1: Performance (Functional)
The system must improve the acceleration and top-speed of the vehicle without impacting braking capabilities.

### L1: Increase downforce when traction limited (Functional)
The control subsystem shall increase the downforce of the car when it is traction limited.

#### D2: Wing increments (Functional)
The control subsystem shall output commands wing position changes in increments of 10%.

### L2: Decrease drag when not traction limited (Functional)
The control subsystem shall decrease drag when the car is not traction limited.

## H2: Identify critical fail (Functional)
In the event of a system critical failure, the failure must be detectable and identifiable.

### L7: Critical fail detection time (Functional)
The diagnostic subsystem shall detect critical failures in at most 50ms.

## H4: No unsafe condition on critical fail (Functional)
In the event of a critical system failure, the vehicle must not be able to enter an unsafe condition.

### L4: Limit speed on critical fail (Functional)
In the event of a critical failure, the control subsystem shall limit the vehicle’s speed to 100 km/h to prevent the vehicle from entering an unsafe condition.

## H5: Converge to safe state (Functional)
In the event of a critical system failure which puts the vehicle in an unsafe condition, the system must help the vehicle converge to a safe condition.

### L5: Prevent acceleration on critical fail (Functional)
In the event of a critical failure which puts the vehicle in an unsafe scenario, the control subsystem shall prevent any vehicle acceleration in order to slow the vehicle to a safe speed even if the driver doesn’t apply the brakes.

## H6: Actuator redundancy (Functional)
The system shall have actuator redundancy.

### D3: Identify non-critical fail (Functional)
In the event of a non-critical failure, the failure should be detectable and identifiable.

## H7: Actuator sensors (Functional)
The system’s actuators should each be monitored by redundant sensors.

## H3: Identify non-critical fail (Functional)
In the event of a non-critical failure, the failure should be detectable and identifiable.

### L8: Non-critical fail detection time (Functional)
The diagnostic subsystem should detect non-critical failures in at most 50 ms.

## L3: Failure signal (Functional)
In the event of a failure, the diagnostic subsystem shall output an 8-bit signal detailing the specific error.

### D1: Diagnostics flag (Functional)
The 8-bit error code signal that is outputted by the diagnostic subsystem shall have a critical failure “flag” on the left-most (most significant) bit.

## L6: Operating rate (Functional)
The system shall operate at a 15ms rate.
